;;; 3A - True 3D Arc for AutoCAD
;;; Copyright (c) 2026 Dzmitry Tsiapkin. All rights reserved.
;;; Author: Dzmitry Tsiapkin
;;; All geometry helpers consume WCS 3D points. No system variables changed.
(defun a3:sub (a b) (mapcar '- a b))
(defun a3:add (a b) (mapcar '+ a b))
(defun a3:mul (k a) (mapcar '(lambda (x) (* k x)) a))
(defun a3:dot (a b) (apply '+ (mapcar '* a b)))
(defun a3:cross (a b)
  (list (- (* (cadr a) (caddr b)) (* (caddr a) (cadr b)))
        (- (* (caddr a) (car b)) (* (car a) (caddr b)))
        (- (* (car a) (cadr b)) (* (cadr a) (car b)))))
;; Scaled norm avoids squaring raw surveying coordinates or tiny lengths.
(defun a3:norm (a / m b)
  (setq m (apply 'max (mapcar 'abs a)))
  (if (= m 0.0) 0.0
    (progn (setq b (a3:mul (/ 1.0 m) a))
           (* m (sqrt (a3:dot b b))))))
(defun a3:coordscale (pts)
  (apply 'max (mapcar '(lambda (p) (apply 'max (mapcar 'abs p))) pts)))

;; Result: (center radius unit-normal linear-tolerance), or nil.
;; Longest edge normalization makes the area test dimensionless.
(defun a3:circle (p q r / u v w s floorlen a b n nn h c rad tol)
  (setq u (a3:sub q p) v (a3:sub r p) w (a3:sub r q)
        s (max (a3:norm u) (a3:norm v) (a3:norm w))
        floorlen (* 64.0 2.220446049250313e-16
                    (a3:coordscale (list p q r))))
  (if (and (> s 0.0)
           (> (min (a3:norm u) (a3:norm v) (a3:norm w)) floorlen))
    (progn
      (setq a (a3:mul (/ 1.0 s) u) b (a3:mul (/ 1.0 s) v)
            n (a3:cross a b) nn (a3:norm n))
      ;; Reject area/longest-edge^2 <= 1e-8, or unresolved altitude.
      (if (and (> nn 1e-8) (> (* nn s) floorlen))
        (progn
          (setq h (a3:mul (/ 0.5 nn nn)
                    (a3:add (a3:mul (a3:dot a a) (a3:cross b n))
                            (a3:mul (a3:dot b b) (a3:cross n a))))
                c (a3:add p (a3:mul s h))
                rad (a3:norm (a3:sub c p))
                n (a3:mul (/ 1.0 nn) n)
                tol (+ (* 128.0 2.220446049250313e-16
                          (a3:coordscale (list p q r c)))
                       (* 1e-9 (max s rad))))
          (if (and (> rad 0.0)
                   (a3:verify (list p q r) c rad n tol))
            (list c rad n tol)))))))

;; Check radius residuals, center/point coplanarity and perpendicularity.
(defun a3:verify (pts c rad n tol / ok p u)
  (setq ok (<= (abs (- (a3:norm n) 1.0)) 1e-10))
  (foreach p pts
    (setq u (a3:sub p c)
          ok (and ok (<= (abs (- (a3:norm u) rad)) tol)
                     (<= (abs (a3:dot u n)) tol))))
  (foreach p (cdr pts)
    (setq u (a3:sub p (car pts))
          ok (and ok (<= (abs (a3:dot u n)) tol))))
  ok)


;; Bounded numeric domain prevents overflow before any geometry calculation.
(defun a3:number (x) (and (numberp x) (= x x) (<= (abs x) 1e100)))
(defun a3:point (p)
  (and (listp p) (= (length p) 3)
       (a3:number (car p)) (a3:number (cadr p)) (a3:number (caddr p))))
(defun a3:wrap (x)
  (setq x (rem x (* 2.0 pi)))
  (if (< x 0.0) (+ x (* 2.0 pi)) x))
(defun a3:angle (p c n / v)
  (setq v (trans (a3:sub p c) 0 n T))
  (a3:wrap (atan (cadr v) (car v))))
(defun a3:angles (p q r c n)
  (list (a3:angle p c n) (a3:angle q c n) (a3:angle r c n)))
(defun a3:inside (start middle end budget / span offset)
  (setq span (a3:wrap (- end start)) offset (a3:wrap (- middle start)))
  (and (> span budget) (< span (- (* 2.0 pi) budget))
       (> offset budget) (< offset (- span budget))))
;; Result: (center radius normal linear-tolerance start end angular-budget).
(defun a3:solve (p q r / sol c rad n tol ang budget)
  (if (and (a3:point p) (a3:point q) (a3:point r)
           (> (a3:norm (a3:sub q p)) 1e-100)
           (> (a3:norm (a3:sub r p)) 1e-100)
           (> (a3:norm (a3:sub r q)) 1e-100)
           (setq sol (a3:circle p q r)))
    (progn
      (setq c (car sol) rad (cadr sol) n (caddr sol) tol (nth 3 sol)
            budget (max 1e-12 (* 4.0 (/ tol rad)))
            ang (a3:angles p q r c n))
      (if (not (a3:inside (car ang) (cadr ang) (caddr ang) budget))
        (setq n (a3:mul -1.0 n) ang (a3:angles p q r c n)))
      (if (and (a3:point c) (a3:number rad) (> rad 1e-100)
               (a3:inside (car ang) (cadr ang) (caddr ang) budget))
        (list c rad n tol (car ang) (caddr ang) budget)))))
(defun a3:endpoint (c rad n ang)
  (a3:add c (trans (list (* rad (cos ang)) (* rad (sin ang)) 0.0) n 0 T)))
(defun a3:entity-ok (e pts sol / d c rad n start end tol)
  (setq d (entget e) rad (cdr (assoc 40 d)) n (cdr (assoc 210 d))
        start (cdr (assoc 50 d)) end (cdr (assoc 51 d)) tol (nth 3 sol))
  (and (= (cdr (assoc 0 d)) "ARC")
       (a3:number rad) (> rad 1e-100) (a3:point n)
       (a3:point (cdr (assoc 10 d)))
       (a3:number start) (a3:number end)
       (<= (a3:norm (a3:sub n (caddr sol))) 1e-10)
       (setq c (trans (cdr (assoc 10 d)) e 0)) (a3:point c)
       (<= (a3:norm (a3:sub c (car sol))) tol)
       (<= (abs (- rad (cadr sol))) tol)
       (a3:verify pts c rad n tol)
       (<= (a3:norm (a3:sub (car pts) (a3:endpoint c rad n start))) tol)
       (<= (a3:norm (a3:sub (caddr pts) (a3:endpoint c rad n end))) tol)
       (a3:inside start (a3:angle (cadr pts) c n) end (nth 6 sol))))
(defun a3:make (sol)
  (entmake (list '(0 . "ARC") (cons 8 (getvar "CLAYER"))
    (cons 10 (trans (car sol) 0 (caddr sol))) (cons 40 (cadr sol))
    (cons 50 (nth 4 sol)) (cons 51 (nth 5 sol)) (cons 210 (caddr sol)))))
(defun c:3A (/ *error* pending old p q r sol)
  (defun *error* (msg)
    (if (and pending (not (eq pending old)) (entget pending)) (entdel pending))
    (if (wcmatch (strcase msg) "*CANCEL*,*QUIT*,*BREAK*")
      (princ "\n3A: Cancelled.")
      (princ (strcat "\n3A: Cannot create arc. " msg))) (princ))
  (cond
    ((not (and (setq p (getpoint "\nSpecify arc start point:"))
               (setq q (getpoint "\nSpecify point on arc:"))
               (setq r (getpoint "\nSpecify arc end point:"))))
      (princ "\n3A: Cancelled. Three points are required."))
    (T
      (setq p (trans p 1 0) q (trans q 1 0) r (trans r 1 0) sol (a3:solve p q r))
      (cond
        ((not sol) (princ "\n3A: Cannot create arc. Points are duplicate, nearly collinear, unresolved, or outside the supported numeric range."))
        (T (setq old (entlast))
          (if (a3:make sol)
            (progn (setq pending (entlast))
              (if (and pending (not (eq pending old)) (a3:entity-ok pending (list p q r) sol))
                (progn (setq pending nil) (princ "\n3A: 3D arc created successfully."))
                (progn
                  (if (and pending (not (eq pending old))) (entdel pending))
                  (setq pending nil) (princ "\n3A: Cannot create arc. Entity verification failed."))))
            (princ "\n3A: Cannot create arc. Entity creation failed."))))))
  (princ))
(princ "\n3A loaded. Type 3A to create a true 3D arc.") (princ)
