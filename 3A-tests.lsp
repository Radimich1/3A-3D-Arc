;;; 3A native ARC regression tests. Load 3A.lsp first, then run 3ATEST.
;;; Copyright (c) 2026 Dzmitry Tsiapkin. All rights reserved.
;;; Creates and removes its own entities only; does not change UCS or settings.
(defun a3t:assert (label ok)
  (if ok (setq a3t:passed (1+ a3t:passed)) (setq a3t:failed (1+ a3t:failed)))
  (princ (strcat "\n" (if ok "PASS " "FAIL ") label)))
(defun a3t:point (c radius x y angle)
  (mapcar '+ c (mapcar '(lambda (u v) (* radius (+ (* u (cos angle)) (* v (sin angle))))) x y)))
;; Independent endpoint and arc-length oracle using known fixture center/frame.
(defun a3t:case (label c radius x y start sweep / pts sol e d oc n a b wc ep1 ep3 tol ok)
  (setq pts (mapcar '(lambda (angle) (a3t:point c radius x y angle))
                    (list start (+ start (* 0.43 sweep)) (+ start sweep)))
        sol (apply 'a3:solve pts) ok nil)
  (if (and sol (a3:make sol))
    (progn
      (setq e (entlast) a3t:pending e d (entget e) oc (cdr (assoc 10 d))
            n (cdr (assoc 210 d)) a (cdr (assoc 50 d)) b (cdr (assoc 51 d))
            wc (trans oc e 0)
            ep1 (trans (mapcar '+ oc (list (* (cdr (assoc 40 d)) (cos a)) (* (cdr (assoc 40 d)) (sin a)) 0.0)) e 0)
            ep3 (trans (mapcar '+ oc (list (* (cdr (assoc 40 d)) (cos b)) (* (cdr (assoc 40 d)) (sin b)) 0.0)) e 0)
            tol (max (* radius 1e-7) (* 5e-14 (apply 'max (cons radius (mapcar 'abs c))))))
      (setq ok (and (= (cdr (assoc 0 d)) "ARC")
        (<= (distance wc c) tol) (<= (abs (- (cdr (assoc 40 d)) radius)) tol)
        (<= (distance ep1 (car pts)) tol) (<= (distance ep3 (caddr pts)) tol)
        (<= (abs (- (a3:wrap (- b a)) (abs sweep))) (max 1e-7 (/ tol radius)))
        (a3:entity-ok e pts sol)))
      ;; Swapping endpoints makes the complementary arc; validator must reject it.
      (entmod (subst (cons 51 a) (assoc 51 d) (subst (cons 50 b) (assoc 50 d) d)))
      (a3t:assert (strcat label " rejects complementary sweep") (not (a3:entity-ok e pts sol)))
      (entdel e) (setq a3t:pending nil)))
  (a3t:assert label ok))
(defun c:3ATEST (/ *error* a3t:pending i angle sweep row)
  (defun *error* (msg)
    (if (and a3t:pending (entget a3t:pending)) (entdel a3t:pending))
    (setq a3t:failed (1+ a3t:failed)) (princ (strcat "\nFAIL test error: " msg)) (princ))
  (setq a3t:passed 0 a3t:failed 0)
  (foreach row
    '(("XY minor" (0 0 0) 10 (1 0 0) (0 1 0) 0.0 1.2)
      ("XY semicircle" (0 0 0) 10 (1 0 0) (0 1 0) 0.0 3.141592653589793)
      ("XY major" (0 0 0) 10 (1 0 0) (0 1 0) 0.4 4.8)
      ("Nearly full" (0 0 0) 10 (1 0 0) (0 1 0) 0.3 6.283085307179586)
      ("Clockwise reversed" (0 0 0) 10 (1 0 0) (0 1 0) 5.2 -4.8)
      ("XZ" (1 2 3) 10 (1 0 0) (0 0 1) 0.0 4.8)
      ("YZ" (1 2 3) 10 (0 1 0) (0 0 1) 0.2 2.4)
      ("Inclined" (1 3 4) 6 (0.6 0.8 0) (-0.48 0.36 0.8) 0.3 4.2)
      ("Survey coordinates" (6580000 670000 35) 6 (0.6 0.8 0) (-0.48 0.36 0.8) 0.3 4.2)
      ("Small scale" (0 0 0) 1e-9 (1 0 0) (0 1 0) 0.3 4.2)
      ("Large scale" (0 0 0) 1e80 (1 0 0) (0 1 0) 0.3 4.2)
      ("Tiny scale" (0 0 0) 1e-80 (1 0 0) (0 1 0) 0.3 4.2))
    (apply 'a3t:case row))
  (foreach row
    '(("Duplicate" (0 0 0) (0 0 0) (1 0 0))
      ("Collinear" (0 0 0) (1 0 0) (2 0 0))
      ("Nearly collinear" (0 0 0) (1 0 0) (2 1e-10 0))
      ("Unresolved coordinates" (6580000 670000 35) (6580000.000000001 670000 35) (6580000 670000.000000001 35))
      ("Missing point" nil (1 0 0) (0 1 0))
      ("2D point" (0 0) (1 0 0) (0 1 0))
      ("Non numeric" (0 "x" 0) (1 0 0) (0 1 0))
      ("Out of range" (1e110 0 0) (0 1 0) (0 0 1)))
    (a3t:assert (car row) (not (apply 'a3:solve (cdr row)))))
  ;; Exercises UCS->WCS input conversion in the current (possibly rotated) UCS.
  (a3t:assert "Current UCS round trip"
    (equal '(2.0 3.0 4.0) (trans (trans '(2.0 3.0 4.0) 0 1) 1 0) 1e-9))
  (setq i 0)
  (repeat 120
    (setq angle (* i 0.173) sweep (+ 0.1 (* 0.05 (rem i 120))))
    (if (= (rem i 2) 1) (setq sweep (- sweep)))
    (a3t:case (strcat "Generated " (itoa i)) '(100 -200 30) 7
      '(0.6 0.8 0) '(-0.48 0.36 0.8) angle sweep)
    (setq i (1+ i)))
  (princ (strcat "\n3ATEST: " (itoa a3t:passed) " passed; " (itoa a3t:failed) " failed.")) (princ))
(princ "\n3A tests loaded. Type 3ATEST.") (princ)
